(setq *aab:assignments* '(
    ("21BC631" "PONTOS_ELE_INTERFONE_VIDEO_PORTEIRO" "PONTO")
    ("21BD860" "PONTOS_ELE_INTERFONE_VIDEO_PORTEIRO" "PONTO")
    ("21BC62E" "PONTOS_ELE_INTERNET" "PONTO")
    ("21ADDC2" "PONTOS_ELE_INTERRUPTOR" "PONTO")
    ("21ADDCB" "PONTOS_ELE_INTERRUPTOR" "PONTO")
    ("21ADDCE" "PONTOS_ELE_INTERRUPTOR" "PONTO")
    ("21AE332" "PONTOS_ELE_INTERRUPTOR" "PONTO")
    ("21AEA70" "PONTOS_ELE_INTERRUPTOR" "PONTO")
    ("21AEBD8" "PONTOS_ELE_INTERRUPTOR" "PONTO")
    ("21AEBEC" "PONTOS_ELE_INTERRUPTOR" "PONTO")
    ("21AF02E" "PONTOS_ELE_INTERRUPTOR" "PONTO")
    ("21AF198" "PONTOS_ELE_INTERRUPTOR" "PONTO")
    ("21AF1A7" "PONTOS_ELE_INTERRUPTOR" "PONTO")
    ("21AF1AA" "PONTOS_ELE_INTERRUPTOR" "PONTO")
    ("21AF1AB" "PONTOS_ELE_INTERRUPTOR" "PONTO")
    ("21AF1D6" "PONTOS_ELE_INTERRUPTOR" "PONTO")
    ("21AF2F7" "PONTOS_ELE_INTERRUPTOR" "PONTO")
    ("21AF30D" "PONTOS_ELE_INTERRUPTOR" "PONTO")
    ("21AF319" "PONTOS_ELE_INTERRUPTOR" "PONTO")
    ("21AF31C" "PONTOS_ELE_INTERRUPTOR" "PONTO")
    ("21AF481" "PONTOS_ELE_INTERRUPTOR" "PONTO")
    ("21AF7E2" "PONTOS_ELE_INTERRUPTOR" "PONTO")
    ("21AF7E8" "PONTOS_ELE_INTERRUPTOR" "PONTO")
    ("21AF8D7" "PONTOS_ELE_INTERRUPTOR" "PONTO")
    ("21AF9F9" "PONTOS_ELE_INTERRUPTOR" "PONTO")
    ("21AFABC" "PONTOS_ELE_INTERRUPTOR" "PONTO")
    ("21AFB1D" "PONTOS_ELE_INTERRUPTOR" "PONTO")
    ("21AFCF1" "PONTOS_ELE_INTERRUPTOR" "PONTO")
    ("21AFCFE" "PONTOS_ELE_INTERRUPTOR" "PONTO")
    ("21AFD03" "PONTOS_ELE_INTERRUPTOR" "PONTO")
    ("21AFD25" "PONTOS_ELE_INTERRUPTOR" "PONTO")
    ("21AFD26" "PONTOS_ELE_INTERRUPTOR" "PONTO")
    ("21BC4D5" "PONTOS_ELE_INTERRUPTOR" "PONTO")
    ("21BC4FC" "PONTOS_ELE_INTERRUPTOR" "PONTO")
    ("21BC6D2" "PONTOS_ELE_INTERRUPTOR" "PONTO")
    ("21BCE3A" "PONTOS_ELE_INTERRUPTOR" "PONTO")
    ("21BCE4B" "PONTOS_ELE_INTERRUPTOR" "PONTO")
    ("21BCE4D" "PONTOS_ELE_INTERRUPTOR" "PONTO")
    ("21BD4FC" "PONTOS_ELE_INTERRUPTOR" "PONTO")
    ("21BD5CC" "PONTOS_ELE_INTERRUPTOR" "PONTO")
    ("21BD7F9" "PONTOS_ELE_INTERRUPTOR" "PONTO")
    ("21F5B21" "PONTOS_ELE_INTERRUPTOR" "PONTO")
    ("21F5B3A" "PONTOS_ELE_INTERRUPTOR" "PONTO")
    ("21FF6E9" "PONTOS_ELE_INTERRUPTOR" "PONTO")
    ("21FF768" "PONTOS_ELE_INTERRUPTOR" "PONTO")
    ("21FFC2B" "PONTOS_ELE_INTERRUPTOR" "PONTO")
    ("21FFC35" "PONTOS_ELE_INTERRUPTOR" "PONTO")
    ("21FFC5B" "PONTOS_ELE_INTERRUPTOR" "PONTO")
    ("2209D81" "PONTOS_ELE_INTERRUPTOR" "PONTO")
    ("21BC64A" "PONTOS_ELE_PONTO_DE_AUTOMACAO_CORTINAS_E_PERSIANAS" "PONTO")
    ("21BC64B" "PONTOS_ELE_PONTO_DE_AUTOMACAO_CORTINAS_E_PERSIANAS" "PONTO")
    ("21BC64C" "PONTOS_ELE_PONTO_DE_AUTOMACAO_CORTINAS_E_PERSIANAS" "PONTO")
    ("23199C8" "PONTOS_ELE_PONTO_DE_AUTOMACAO_CORTINAS_E_PERSIANAS" "PONTO")
    ("21AFD60" "PONTOS_ELE_PONTO_DE_GAS" "PONTO")
    ("21BC735" "PONTOS_ELE_PONTO_DE_GAS" "PONTO")
    ("21BCE62" "PONTOS_ELE_PONTO_DE_GAS" "PONTO")
    ("21BC62F" "PONTOS_ELE_QUADRO_DE_AUTOMACAO" "PONTO")
    ("21BC630" "PONTOS_ELE_QUADRO_DE_DISTRIBUICAO_DE_CIRCUITO" "PONTO")
    ("21BC62C" "PONTOS_ELE_QUADRO_DE_ENERGIA_SOLAR" "PONTO")
    ("21BC62D" "PONTOS_ELE_RACK_VDI" "PONTO")
    ("21AFD61" "PONTOS_ELE_TOMADA_ALTA" "PONTO")
    ("21ADDC6" "PONTOS_ELE_TOMADA_BAIXA" "PONTO")
    ("21ADDCF" "PONTOS_ELE_TOMADA_BAIXA" "PONTO")
    ("21AEBCA" "PONTOS_ELE_TOMADA_BAIXA" "PONTO")
    ("21AF18C" "PONTOS_ELE_TOMADA_BAIXA" "PONTO")
    ("21AF31D" "PONTOS_ELE_TOMADA_BAIXA" "PONTO")
    ("21AF332" "PONTOS_ELE_TOMADA_BAIXA" "PONTO")
    ("21AFA9D" "PONTOS_ELE_TOMADA_BAIXA" "PONTO")
    ("21AFCF2" "PONTOS_ELE_TOMADA_BAIXA" "PONTO")
    ("21AFCF3" "PONTOS_ELE_TOMADA_BAIXA" "PONTO")
    ("21AFCFF" "PONTOS_ELE_TOMADA_BAIXA" "PONTO")
    ("21AFD07" "PONTOS_ELE_TOMADA_BAIXA" "PONTO")
    ("21AFD09" "PONTOS_ELE_TOMADA_BAIXA" "PONTO")
    ("21AFD0F" "PONTOS_ELE_TOMADA_BAIXA" "PONTO")
    ("21AFD10" "PONTOS_ELE_TOMADA_BAIXA" "PONTO")
    ("21AFD14" "PONTOS_ELE_TOMADA_BAIXA" "PONTO")
    ("21AFD15" "PONTOS_ELE_TOMADA_BAIXA" "PONTO")
    ("21AFD23" "PONTOS_ELE_TOMADA_BAIXA" "PONTO")
    ("21AFD2B" "PONTOS_ELE_TOMADA_BAIXA" "PONTO")
    ("21AFD2D" "PONTOS_ELE_TOMADA_BAIXA" "PONTO")
    ("21AFD62" "PONTOS_ELE_TOMADA_BAIXA" "PONTO")
    ("21AFD95" "PONTOS_ELE_TOMADA_BAIXA" "PONTO")
    ("21BBE5D" "PONTOS_ELE_TOMADA_BAIXA" "PONTO")
    ("21BC4F8" "PONTOS_ELE_TOMADA_BAIXA" "PONTO")
    ("21BC6F4" "PONTOS_ELE_TOMADA_BAIXA" "PONTO")
    ("21BC6FE" "PONTOS_ELE_TOMADA_BAIXA" "PONTO")
    ("21BC728" "PONTOS_ELE_TOMADA_BAIXA" "PONTO")
    ("21BC72B" "PONTOS_ELE_TOMADA_BAIXA" "PONTO")
    ("21BC736" "PONTOS_ELE_TOMADA_BAIXA" "PONTO")
    ("21BC738" "PONTOS_ELE_TOMADA_BAIXA" "PONTO")
    ("21BCE3B" "PONTOS_ELE_TOMADA_BAIXA" "PONTO")
    ("21BCE4F" "PONTOS_ELE_TOMADA_BAIXA" "PONTO")
    ("21BCE5E" "PONTOS_ELE_TOMADA_BAIXA" "PONTO")
    ("21BD4E1" "PONTOS_ELE_TOMADA_BAIXA" "PONTO")
    ("21BD4EE" "PONTOS_ELE_TOMADA_BAIXA" "PONTO")
    ("21BD507" "PONTOS_ELE_TOMADA_BAIXA" "PONTO")
    ("21BD50B" "PONTOS_ELE_TOMADA_BAIXA" "PONTO")
    ("21BD7FA" "PONTOS_ELE_TOMADA_BAIXA" "PONTO")
    ("21BD7FD" "PONTOS_ELE_TOMADA_BAIXA" "PONTO")
    ("21BD7FE" "PONTOS_ELE_TOMADA_BAIXA" "PONTO")
    ("21AFD2E" "PONTOS_ELE_TOMADA_DUPLA_20A_220V" "PONTO")
    ("21BC708" "PONTOS_ELE_TOMADA_DUPLA_20A_220V" "PONTO")
    ("21ADDCA" "PONTOS_ELE_TOMADA_DUPLA_CABECEIRA" "PONTO")
    ("21ADDCD" "PONTOS_ELE_TOMADA_DUPLA_CABECEIRA" "PONTO")
    ("21AEBD7" "PONTOS_ELE_TOMADA_DUPLA_CABECEIRA" "PONTO")
    ("21AF1A6" "PONTOS_ELE_TOMADA_DUPLA_CABECEIRA" "PONTO")
    ("21AF1A9" "PONTOS_ELE_TOMADA_DUPLA_CABECEIRA" "PONTO")
    ("21AF318" "PONTOS_ELE_TOMADA_DUPLA_CABECEIRA" "PONTO")
    ("21AF31B" "PONTOS_ELE_TOMADA_DUPLA_CABECEIRA" "PONTO")
    ("21AF7E7" "PONTOS_ELE_TOMADA_DUPLA_CABECEIRA" "PONTO")
    ("21AE333" "PONTOS_ELE_TOMADA_MEDIA" "PONTO")
    ("21AE337" "PONTOS_ELE_TOMADA_MEDIA" "PONTO")
    ("21AEA71" "PONTOS_ELE_TOMADA_MEDIA" "PONTO")
    ("21AEA7A" "PONTOS_ELE_TOMADA_MEDIA" "PONTO")
    ("21AF02C" "PONTOS_ELE_TOMADA_MEDIA" "PONTO")
    ("21AF02F" "PONTOS_ELE_TOMADA_MEDIA" "PONTO")
    ("21AF47B" "PONTOS_ELE_TOMADA_MEDIA" "PONTO")
    ("21AF47D" "PONTOS_ELE_TOMADA_MEDIA" "PONTO")
    ("21AF8DB" "PONTOS_ELE_TOMADA_MEDIA" "PONTO")
    ("21AFAA2" "PONTOS_ELE_TOMADA_MEDIA" "PONTO")
    ("21AFABB" "PONTOS_ELE_TOMADA_MEDIA" "PONTO")
    ("21AFB14" "PONTOS_ELE_TOMADA_MEDIA" "PONTO")
    ("21AFD8F" "PONTOS_ELE_TOMADA_MEDIA" "PONTO")
    ("21AFDA6" "PONTOS_ELE_TOMADA_MEDIA" "PONTO")
    ("21AFDA7" "PONTOS_ELE_TOMADA_MEDIA" "PONTO")
    ("21AFE2D" "PONTOS_ELE_TOMADA_MEDIA" "PONTO")
    ("21BBE66" "PONTOS_ELE_TOMADA_MEDIA" "PONTO")
    ("21BBE67" "PONTOS_ELE_TOMADA_MEDIA" "PONTO")
    ("21BC500" "PONTOS_ELE_TOMADA_MEDIA" "PONTO")
    ("21BC715" "PONTOS_ELE_TOMADA_MEDIA" "PONTO")
    ("21BC717" "PONTOS_ELE_TOMADA_MEDIA" "PONTO")
    ("21BC718" "PONTOS_ELE_TOMADA_MEDIA" "PONTO")
    ("21BC7D3" "PONTOS_ELE_TOMADA_MEDIA" "PONTO")
    ("21BCE3C" "PONTOS_ELE_TOMADA_MEDIA" "PONTO")
    ("21BCE50" "PONTOS_ELE_TOMADA_MEDIA" "PONTO")
    ("21BCE5F" "PONTOS_ELE_TOMADA_MEDIA" "PONTO")
    ("21BD4E2" "PONTOS_ELE_TOMADA_MEDIA" "PONTO")
    ("21BD4EF" "PONTOS_ELE_TOMADA_MEDIA" "PONTO")
    ("21BD508" "PONTOS_ELE_TOMADA_MEDIA" "PONTO")
    ("21BD50C" "PONTOS_ELE_TOMADA_MEDIA" "PONTO")
    ("22FACF7" "PONTOS_ELE_TOMADA_MEDIA" "PONTO")
    ("22FAD48" "PONTOS_ELE_TOMADA_MEDIA" "PONTO")
    ("22FAD6B" "PONTOS_ELE_TOMADA_MEDIA" "PONTO")
    ("22FAD6D" "PONTOS_ELE_TOMADA_MEDIA" "PONTO")
    ("22FAD6E" "PONTOS_ELE_TOMADA_MEDIA" "PONTO")
    ("22FAD6F" "PONTOS_ELE_TOMADA_MEDIA" "PONTO")
    ("22FAD75" "PONTOS_ELE_TOMADA_MEDIA" "PONTO")
    ("22FAD76" "PONTOS_ELE_TOMADA_MEDIA" "PONTO")
    ("21BCC60" "PONTOS_ELE_TOMADA_NO_TETO" "PONTO")
    ("21BCC61" "PONTOS_ELE_TOMADA_NO_TETO" "PONTO")
    ("21BCC63" "PONTOS_ELE_TOMADA_NO_TETO" "PONTO")
    ("21BCC67" "PONTOS_ELE_TOMADA_NO_TETO" "PONTO")
    ("21BCC68" "PONTOS_ELE_TOMADA_NO_TETO" "PONTO")
    ("21BCC69" "PONTOS_ELE_TOMADA_NO_TETO" "PONTO")
    ("21BCC6A" "PONTOS_ELE_TOMADA_NO_TETO" "PONTO")
    ("21BCC6B" "PONTOS_ELE_TOMADA_NO_TETO" "PONTO")
    ("21BCC74" "PONTOS_ELE_TOMADA_NO_TETO" "PONTO")
    ("21BCC75" "PONTOS_ELE_TOMADA_NO_TETO" "PONTO")
    ("21BCE35" "PONTOS_ELE_TOMADA_NO_TETO" "PONTO")
    ("21BCE37" "PONTOS_ELE_TOMADA_NO_TETO" "PONTO")
    ("21BCE38" "PONTOS_ELE_TOMADA_NO_TETO" "PONTO")
    ("21BCE39" "PONTOS_ELE_TOMADA_NO_TETO" "PONTO")
    ("22FAD9B" "PONTOS_ELE_TOMADA_NO_TETO" "PONTO")
    ("22FAD9C" "PONTOS_ELE_TOMADA_NO_TETO" "PONTO")
    ("2307C49" "PONTOS_ELE_TOMADA_NO_TETO" "PONTO")
    ("21BD7FB" "PONTOS_ELE_TOMADA_PARA_ABASTECIMENTO_DE_VEICULOS" "PONTO")
    ("21ADDBF" "PONTOS_ELE_TOMADA_PARA_AR_CONDICIONADO_DE_PAREDE" "PONTO")
    ("21AEBC4" "PONTOS_ELE_TOMADA_PARA_AR_CONDICIONADO_DE_PAREDE" "PONTO")
    ("21AF199" "PONTOS_ELE_TOMADA_PARA_AR_CONDICIONADO_DE_PAREDE" "PONTO")
    ("21AF30A" "PONTOS_ELE_TOMADA_PARA_AR_CONDICIONADO_DE_PAREDE" "PONTO")
    ("21AF7CD" "PONTOS_ELE_TOMADA_PARA_AR_CONDICIONADO_DE_PAREDE" "PONTO")
    ("21AFA1C" "PONTOS_ELE_TOMADA_PARA_AR_CONDICIONADO_DE_PAREDE" "PONTO")
    ("21AFD04" "PONTOS_ELE_TOMADA_PARA_AR_CONDICIONADO_DE_PAREDE" "PONTO")
    ("21AFD64" "PONTOS_ELE_TOMADA_PARA_AR_CONDICIONADO_DE_PAREDE" "PONTO")
    ("21AFD19" "PONTOS_ELE_TOMADA_PARA_AR_CONDICIONADO_DE_TETO" "PONTO")
    ("21AFD1C" "PONTOS_ELE_TOMADA_PARA_AR_CONDICIONADO_DE_TETO" "PONTO")
    ("21AFD1D" "PONTOS_ELE_TOMADA_PARA_VENTILADOR_DE_TETO" "PONTO")
    ("21AFD1E" "PONTOS_ELE_TOMADA_PARA_VENTILADOR_DE_TETO" "PONTO")
    ("21AFD1F" "PONTOS_ELE_TOMADA_PARA_VENTILADOR_DE_TETO" "PONTO")
    ("21AFD20" "PONTOS_ELE_TOMADA_PARA_VENTILADOR_DE_TETO" "PONTO")
    ("21AFD21" "PONTOS_ELE_TOMADA_PARA_VENTILADOR_DE_TETO" "PONTO")
    ("21AFD22" "PONTOS_ELE_TOMADA_PARA_VENTILADOR_DE_TETO" "PONTO")
    ("22E9035" "PONTOS_ELE_TOMADA_PARA_VENTILADOR_DE_TETO" "PONTO")
    ("21ADDC7" "PONTOS_ELE_TOMADA_REDE_DADOS_LOGICA" "PONTO")
    ("21ADDC9" "PONTOS_ELE_TOMADA_REDE_DADOS_LOGICA" "PONTO")
    ("21ADDCC" "PONTOS_ELE_TOMADA_REDE_DADOS_LOGICA" "PONTO")
    ("21AEBCB" "PONTOS_ELE_TOMADA_REDE_DADOS_LOGICA" "PONTO")
    ("21AEBD6" "PONTOS_ELE_TOMADA_REDE_DADOS_LOGICA" "PONTO")
    ("21AF18D" "PONTOS_ELE_TOMADA_REDE_DADOS_LOGICA" "PONTO")
    ("21AF1A5" "PONTOS_ELE_TOMADA_REDE_DADOS_LOGICA" "PONTO")
    ("21AF1A8" "PONTOS_ELE_TOMADA_REDE_DADOS_LOGICA" "PONTO")
    ("21AF317" "PONTOS_ELE_TOMADA_REDE_DADOS_LOGICA" "PONTO")
    ("21AF31A" "PONTOS_ELE_TOMADA_REDE_DADOS_LOGICA" "PONTO")
    ("21AF31E" "PONTOS_ELE_TOMADA_REDE_DADOS_LOGICA" "PONTO")
    ("21AF7E6" "PONTOS_ELE_TOMADA_REDE_DADOS_LOGICA" "PONTO")
    ("21AFA9E" "PONTOS_ELE_TOMADA_REDE_DADOS_LOGICA" "PONTO")
    ("21AE32D" "PONTOS_HID_CHUVEIRO" "PONTO")
    ("21AEA41" "PONTOS_HID_CHUVEIRO" "PONTO")
    ("21AEFFA" "PONTOS_HID_CHUVEIRO" "PONTO")
    ("21AF487" "PONTOS_HID_CHUVEIRO" "PONTO")
    ("21AF4E5" "PONTOS_HID_CHUVEIRO" "PONTO")
    ("21AF8C5" "PONTOS_HID_CHUVEIRO" "PONTO")
    ("21AFB1B" "PONTOS_HID_CHUVEIRO" "PONTO")
    ("21BCF78" "PONTOS_HID_CHUVEIRO" "PONTO")
    ("21AE32B" "PONTOS_HID_DESVIADOR_CHUVEIRO" "PONTO")
    ("21AEA3F" "PONTOS_HID_DESVIADOR_CHUVEIRO" "PONTO")
    ("21AEFF8" "PONTOS_HID_DESVIADOR_CHUVEIRO" "PONTO")
    ("21AF485" "PONTOS_HID_DESVIADOR_CHUVEIRO" "PONTO")
    ("21AF8C6" "PONTOS_HID_DESVIADOR_CHUVEIRO" "PONTO")
    ("21AFB19" "PONTOS_HID_DESVIADOR_CHUVEIRO" "PONTO")
    ("21AE32F" "PONTOS_HID_DUCHA_HIGIENICA" "PONTO")
    ("21AEA5B" "PONTOS_HID_DUCHA_HIGIENICA" "PONTO")
    ("21AF005" "PONTOS_HID_DUCHA_HIGIENICA" "PONTO")
    ("21AF483" "PONTOS_HID_DUCHA_HIGIENICA" "PONTO")
    ("21AF8D4" "PONTOS_HID_DUCHA_HIGIENICA" "PONTO")
    ("21AFB17" "PONTOS_HID_DUCHA_HIGIENICA" "PONTO")
    ("21AFD28" "PONTOS_HID_LAVA_LOUCAS" "PONTO")
    ("21AFE2C" "PONTOS_HID_PONTO_DE_AGUA_PARA_GELADEIRA" "PONTO")
    ("21BC714" "PONTOS_HID_PONTO_DE_AGUA_PARA_GELADEIRA" "PONTO")
    ("21BC716" "PONTOS_HID_PONTO_DE_AGUA_PARA_GELADEIRA" "PONTO")
    ("21BC72F" "PONTOS_HID_PONTO_DE_AGUA_PARA_GELADEIRA" "PONTO")
    ("21AE32E" "PONTOS_HID_PONTO_PARA_BACIA_SANITARIA" "PONTO")
    ("21AEA5A" "PONTOS_HID_PONTO_PARA_BACIA_SANITARIA" "PONTO")
    ("21AF004" "PONTOS_HID_PONTO_PARA_BACIA_SANITARIA" "PONTO")
    ("21AF482" "PONTOS_HID_PONTO_PARA_BACIA_SANITARIA" "PONTO")
    ("21AF8D3" "PONTOS_HID_PONTO_PARA_BACIA_SANITARIA" "PONTO")
    ("21AFB16" "PONTOS_HID_PONTO_PARA_BACIA_SANITARIA" "PONTO")
    ("21BCE53" "PONTOS_HID_PONTO_PARA_IRRIGACAO_DE_JARDIM" "PONTO")
    ("21BCE56" "PONTOS_HID_PONTO_PARA_IRRIGACAO_DE_JARDIM" "PONTO")
    ("21BCE57" "PONTOS_HID_PONTO_PARA_IRRIGACAO_DE_JARDIM" "PONTO")
    ("21BCE58" "PONTOS_HID_PONTO_PARA_IRRIGACAO_DE_JARDIM" "PONTO")
    ("21BCE59" "PONTOS_HID_PONTO_PARA_IRRIGACAO_DE_JARDIM" "PONTO")
    ("21BCE5A" "PONTOS_HID_PONTO_PARA_IRRIGACAO_DE_JARDIM" "PONTO")
    ("21BC4FB" "PONTOS_HID_PONTO_PARA_MAQUINA_DE_LAVAR" "PONTO")
    ("21AF4E6" "PONTOS_HID_PONTO_PARA_REGISTRO_DE_CHUVEIRO_DE_TETO" "PONTO")
    ("21AF4FF" "PONTOS_HID_PONTO_PARA_REGISTRO_DE_CHUVEIRO_DE_TETO" "PONTO")
    ("21AF518" "PONTOS_HID_PONTO_PARA_REGISTRO_DE_CHUVEIRO_DE_TETO" "PONTO")
    ("21AFD9C" "PONTOS_HID_PURIFICADOR" "PONTO")
    ("21BC71A" "PONTOS_HID_PURIFICADOR" "PONTO")
    ("21AE330" "PONTOS_HID_RALO_10X10CM" "PONTO")
    ("21AEA5C" "PONTOS_HID_RALO_10X10CM" "PONTO")
    ("21AF006" "PONTOS_HID_RALO_10X10CM" "PONTO")
    ("21AF484" "PONTOS_HID_RALO_10X10CM" "PONTO")
    ("21AF8D5" "PONTOS_HID_RALO_10X10CM" "PONTO")
    ("21AFB18" "PONTOS_HID_RALO_10X10CM" "PONTO")
    ("21AE320" "PONTOS_HID_RALO_LINEAR" "PONTO")
    ("21AEA00" "PONTOS_HID_RALO_LINEAR" "PONTO")
    ("21AEFA4" "PONTOS_HID_RALO_LINEAR" "PONTO")
    ("21AF488" "PONTOS_HID_RALO_LINEAR" "PONTO")
    ("21AF8C8" "PONTOS_HID_RALO_LINEAR" "PONTO")
    ("21AFB1C" "PONTOS_HID_RALO_LINEAR" "PONTO")
    ("21BC5AB" "PONTOS_HID_RALO_LINEAR" "PONTO")
    ("21BCF79" "PONTOS_HID_RALO_LINEAR" "PONTO")
    ("21BCE5C" "PONTOS_HID_TORNEIRA_DE_JARDIM" "PONTO")
    ("21BCE5D" "PONTOS_HID_TORNEIRA_DE_JARDIM" "PONTO")
    ("21BD4F2" "PONTOS_HID_TORNEIRA_DE_JARDIM" "PONTO")
    ("21BD4FD" "PONTOS_HID_TORNEIRA_DE_JARDIM" "PONTO")
    ("21BD86F" "PONTOS_HID_TORNEIRA_DE_JARDIM" "PONTO")
    ("2310B01" "PONTOS_HID_TORNEIRA_DE_JARDIM" "PONTO")
    ("21AE331" "PONTOS_HID_TORNEIRA_DE_MESA" "PONTO")
    ("21AEA66" "PONTOS_HID_TORNEIRA_DE_MESA" "PONTO")
    ("21AF022" "PONTOS_HID_TORNEIRA_DE_MESA" "PONTO")
    ("21AF47F" "PONTOS_HID_TORNEIRA_DE_MESA" "PONTO")
    ("21AF480" "PONTOS_HID_TORNEIRA_DE_MESA" "PONTO")
    ("21AF8D6" "PONTOS_HID_TORNEIRA_DE_MESA" "PONTO")
    ("21AFD2C" "PONTOS_HID_TORNEIRA_DE_MESA" "PONTO")
    ("21BC6FD" "PONTOS_HID_TORNEIRA_DE_MESA" "PONTO")
    ("21BC733" "PONTOS_HID_TORNEIRA_DE_MESA" "PONTO")
    ("22FACF9" "PONTOS_HID_TORNEIRA_DE_MESA" "PONTO")
    ("21BC4F6" "PONTOS_HID_TORNEIRA_DE_PAREDE_TANQUE" "PONTO")
    ("21BC4F7" "PONTOS_HID_TORNEIRA_DE_PAREDE_TANQUE" "PONTO")
    ("21BCE63" "PONTOS_HID_TORNEIRA_DE_PAREDE_TANQUE" "PONTO")
    ("21ADDC0" "PONTOS_ELE_TOMADA_PARA_AR_CONDICIONADO_DE_PAREDE" "COMPONENTE")
    ("21ADDC1" "PONTOS_ELE_TOMADA_PARA_AR_CONDICIONADO_DE_PAREDE" "COMPONENTE")
    ("21ADDC8" "PONTOS_ELE_TOMADA_REDE_DADOS_LOGICA" "COMPONENTE")
    ("21AE338" "PONTOS_ELE_TOMADA_MEDIA" "COMPONENTE")
    ("21AEA72" "PONTOS_ELE_TOMADA_MEDIA" "COMPONENTE")
    ("22FAD71" "PONTOS_ELE_TOMADA_MEDIA" "COMPONENTE")
    ("21AEA7B" "PONTOS_ELE_TOMADA_MEDIA" "COMPONENTE")
    ("21AEBC9" "PONTOS_ELE_TOMADA_MEDIA" "COMPONENTE")
    ("21AEBC5" "PONTOS_ELE_TOMADA_PARA_AR_CONDICIONADO_DE_PAREDE" "COMPONENTE")
    ("21AEBC6" "PONTOS_ELE_TOMADA_PARA_AR_CONDICIONADO_DE_PAREDE" "COMPONENTE")
    ("21AEBC7" "PONTOS_ELE_TOMADA_REDE_DADOS_LOGICA" "COMPONENTE")
    ("21AEBC8" "PONTOS_ELE_TOMADA_REDE_DADOS_LOGICA" "COMPONENTE")
    ("21AEBD5" "PONTOS_ELE_TOMADA_REDE_DADOS_LOGICA" "COMPONENTE")
    ("21AF02D" "PONTOS_ELE_TOMADA_MEDIA" "COMPONENTE")
    ("22FAD72" "PONTOS_ELE_TOMADA_MEDIA" "COMPONENTE")
    ("21AF030" "PONTOS_ELE_TOMADA_MEDIA" "COMPONENTE")
    ("21AF18B" "PONTOS_ELE_TOMADA_MEDIA" "COMPONENTE")
    ("21AF189" "PONTOS_ELE_TOMADA_REDE_DADOS_LOGICA" "COMPONENTE")
    ("21AF18A" "PONTOS_ELE_TOMADA_REDE_DADOS_LOGICA" "COMPONENTE")
    ("21AF18E" "PONTOS_ELE_TOMADA_REDE_DADOS_LOGICA" "COMPONENTE")
    ("21AF19A" "PONTOS_ELE_TOMADA_PARA_AR_CONDICIONADO_DE_PAREDE" "COMPONENTE")
    ("21AF19B" "PONTOS_ELE_TOMADA_PARA_AR_CONDICIONADO_DE_PAREDE" "COMPONENTE")
    ("21AF30B" "PONTOS_ELE_TOMADA_PARA_AR_CONDICIONADO_DE_PAREDE" "COMPONENTE")
    ("21AF30C" "PONTOS_ELE_TOMADA_PARA_AR_CONDICIONADO_DE_PAREDE" "COMPONENTE")
    ("21AF31F" "PONTOS_ELE_TOMADA_REDE_DADOS_LOGICA" "COMPONENTE")
    ("21AF47C" "PONTOS_ELE_TOMADA_MEDIA" "COMPONENTE")
    ("21AF47E" "PONTOS_ELE_TOMADA_MEDIA" "COMPONENTE")
    ("21AF7CE" "PONTOS_ELE_TOMADA_PARA_AR_CONDICIONADO_DE_PAREDE" "COMPONENTE")
    ("21AF7CF" "PONTOS_ELE_TOMADA_PARA_AR_CONDICIONADO_DE_PAREDE" "COMPONENTE")
    ("21AF7E3" "PONTOS_ELE_INTERRUPTOR" "COMPONENTE")
    ("21AF7E4" "PONTOS_ELE_INTERRUPTOR" "COMPONENTE")
    ("21AF8DC" "PONTOS_ELE_TOMADA_MEDIA" "COMPONENTE")
    ("21AFA1D" "PONTOS_ELE_TOMADA_PARA_AR_CONDICIONADO_DE_PAREDE" "COMPONENTE")
    ("21AFA1E" "PONTOS_ELE_TOMADA_PARA_AR_CONDICIONADO_DE_PAREDE" "COMPONENTE")
    ("21AFA9F" "PONTOS_ELE_TOMADA_REDE_DADOS_LOGICA" "COMPONENTE")
    ("21AFD11" "PONTOS_ELE_TOMADA_REDE_DADOS_LOGICA" "COMPONENTE")
    ("21AFD12" "PONTOS_ELE_TOMADA_REDE_DADOS_LOGICA" "COMPONENTE")
    ("21AFD13" "PONTOS_ELE_TOMADA_REDE_DADOS_LOGICA" "COMPONENTE")
    ("21AFAA1" "PONTOS_ELE_TOMADA_MEDIA" "COMPONENTE")
    ("21AFD01" "PONTOS_ELE_TOMADA_BAIXA" "COMPONENTE")
    ("21AFD05" "PONTOS_ELE_TOMADA_PARA_AR_CONDICIONADO_DE_PAREDE" "COMPONENTE")
    ("21AFD06" "PONTOS_ELE_TOMADA_PARA_AR_CONDICIONADO_DE_PAREDE" "COMPONENTE")
    ("21AFD08" "PONTOS_ELE_TOMADA_BAIXA" "COMPONENTE")
    ("21AFD0A" "PONTOS_ELE_TOMADA_BAIXA" "COMPONENTE")
    ("21AFD16" "PONTOS_ELE_TOMADA_BAIXA" "COMPONENTE")
    ("21AFD17" "PONTOS_ELE_TOMADA_PARA_AR_CONDICIONADO_DE_TETO" "COMPONENTE")
    ("21AFD18" "PONTOS_ELE_TOMADA_PARA_AR_CONDICIONADO_DE_TETO" "COMPONENTE")
    ("21AFD1A" "PONTOS_ELE_TOMADA_PARA_AR_CONDICIONADO_DE_TETO" "COMPONENTE")
    ("21AFD1B" "PONTOS_ELE_TOMADA_PARA_AR_CONDICIONADO_DE_TETO" "COMPONENTE")
    ("21AFD24" "PONTOS_ELE_TOMADA_BAIXA" "COMPONENTE")
    ("21AFD2F" "PONTOS_ELE_TOMADA_DUPLA_20A_220V" "COMPONENTE")
    ("21AFD65" "PONTOS_ELE_TOMADA_PARA_AR_CONDICIONADO_DE_PAREDE" "COMPONENTE")
    ("21AFD66" "PONTOS_ELE_TOMADA_PARA_AR_CONDICIONADO_DE_PAREDE" "COMPONENTE")
    ("21AFD98" "PONTOS_ELE_TOMADA_MEDIA" "COMPONENTE")
    ("21AFD99" "PONTOS_ELE_TOMADA_MEDIA" "COMPONENTE")
    ("21AFD96" "PONTOS_ELE_TOMADA_BAIXA" "COMPONENTE")
    ("21AFD97" "PONTOS_ELE_TOMADA_BAIXA" "COMPONENTE")
    ("21AFD9B" "PONTOS_ELE_TOMADA_MEDIA" "COMPONENTE")
    ("21BBE5E" "PONTOS_ELE_TOMADA_BAIXA" "COMPONENTE")
    ("2307C7A" "PONTOS_ELE_TOMADA_MEDIA" "COMPONENTE")
    ("21BC4F9" "PONTOS_ELE_TOMADA_BAIXA" "COMPONENTE")
    ("21BC709" "PONTOS_ELE_TOMADA_DUPLA_20A_220V" "COMPONENTE")
    ("21BC713" "PONTOS_ELE_TOMADA_DUPLA_20A_220V" "COMPONENTE")
    ("21BC719" "PONTOS_ELE_TOMADA_MEDIA" "COMPONENTE")
    ("21BC737" "PONTOS_ELE_TOMADA_BAIXA" "COMPONENTE")
    ("2307C77" "PONTOS_ELE_TOMADA_BAIXA" "COMPONENTE")
    ("2307C78" "PONTOS_ELE_TOMADA_BAIXA" "COMPONENTE")
    ("21BC72A" "PONTOS_ELE_TOMADA_BAIXA" "COMPONENTE")
    ("21BC72D" "PONTOS_ELE_TOMADA_BAIXA" "COMPONENTE")
    ("2307C79" "PONTOS_ELE_TOMADA_BAIXA" "COMPONENTE")
    ("21BC73B" "PONTOS_ELE_TOMADA_BAIXA" "COMPONENTE")
    ("21BCE3E" "PONTOS_ELE_TOMADA_BAIXA" "COMPONENTE")
    ("21BCE3D" "PONTOS_ELE_TOMADA_MEDIA" "COMPONENTE")
    ("21BCE52" "PONTOS_ELE_TOMADA_BAIXA" "COMPONENTE")
    ("21BCE51" "PONTOS_ELE_TOMADA_MEDIA" "COMPONENTE")
    ("21BCE61" "PONTOS_ELE_TOMADA_BAIXA" "COMPONENTE")
    ("21BCE60" "PONTOS_ELE_TOMADA_MEDIA" "COMPONENTE")
    ("21BD4E4" "PONTOS_ELE_TOMADA_BAIXA" "COMPONENTE")
    ("21BD4E3" "PONTOS_ELE_TOMADA_MEDIA" "COMPONENTE")
    ("21BD4F1" "PONTOS_ELE_TOMADA_BAIXA" "COMPONENTE")
    ("21BD4F0" "PONTOS_ELE_TOMADA_MEDIA" "COMPONENTE")
    ("21BD50A" "PONTOS_ELE_TOMADA_BAIXA" "COMPONENTE")
    ("21BD509" "PONTOS_ELE_TOMADA_MEDIA" "COMPONENTE")
    ("21BD50E" "PONTOS_ELE_TOMADA_BAIXA" "COMPONENTE")
    ("21BD50D" "PONTOS_ELE_TOMADA_MEDIA" "COMPONENTE")
    ("21BD7FC" "PONTOS_ELE_TOMADA_BAIXA" "COMPONENTE")
    ("21BD7FF" "PONTOS_ELE_TOMADA_BAIXA" "COMPONENTE")
    ("22FACF8" "PONTOS_ELE_TOMADA_MEDIA" "COMPONENTE")
    ("22FAD49" "PONTOS_ELE_TOMADA_MEDIA" "COMPONENTE")
    ("21AF7E5" "PONTOS_ELE_TOMADA_MEDIA" "COMPONENTE")
    ("22FAD6C" "PONTOS_ELE_TOMADA_MEDIA" "COMPONENTE")
    ("21AE334" "PONTOS_ELE_TOMADA_MEDIA" "COMPONENTE")
    ("22FAD70" "PONTOS_ELE_TOMADA_MEDIA" "COMPONENTE")
    ("21BC501" "PONTOS_ELE_TOMADA_MEDIA" "COMPONENTE")
    ("21AE32C" "PONTOS_HID_DESVIADOR_CHUVEIRO" "COMPONENTE")
    ("21AEA40" "PONTOS_HID_DESVIADOR_CHUVEIRO" "COMPONENTE")
    ("21AEFF9" "PONTOS_HID_DESVIADOR_CHUVEIRO" "COMPONENTE")
    ("21AF486" "PONTOS_HID_DESVIADOR_CHUVEIRO" "COMPONENTE")
    ("21AF8C7" "PONTOS_HID_DESVIADOR_CHUVEIRO" "COMPONENTE")
    ("21AFB1A" "PONTOS_HID_DESVIADOR_CHUVEIRO" "COMPONENTE")))
(setq *aab:removal-rules* '(
    ("02" "INSERT" "NOME DO_DESENHO")
    ("01" "INSERT" "LOGO ICON")
    ("TABELA" "LINE" "")
    ("CHAMADA - cotas" "LINE" "")
    ("TABELA" "LWPOLYLINE" "")
    ("DEFPOINTS" "LWPOLYLINE" "")
    ("CHAMADA - cotas" "INSERT" "CINZA PONTOS")
    ("CHAMADA - cotas" "LEADER" "")
    ("CHAMADA - cotas" "DIMENSION" "")))
(defun aab:csv (value)
  (strcat "\"" (if value value "") "\""))
(defun aab:ensure-layer (name / result)
  (if (not (tblsearch "LAYER" name))
    (setq result
      (entmake
        (list '(0 . "LAYER") '(100 . "AcDbSymbolTableRecord")
          '(100 . "AcDbLayerTableRecord") (cons 2 name)
          '(70 . 0) '(62 . 7) '(6 . "Continuous")))))
  (or (tblsearch "LAYER" name) result))
(defun aab:set-layer (handle layer / entity data pair result)
  (setq entity (handent handle))
  (if (null entity) "AUSENTE"
    (progn
      (aab:ensure-layer layer)
      (setq data (entget entity))
      (setq pair (assoc 8 data))
      (setq result (entmod (subst (cons 8 layer) pair data)))
      (if result "APLICADO" "ERRO"))))
(defun aab:entity-block (data / value)
  (setq value (cdr (assoc 2 data)))
  (if value (strcase value) ""))
(defun aab:protected-layer-p (layer)
  (= (substr (strcase layer) 1 7) "PONTOS_"))
(defun aab:matches-rule-p (data rule / layer type block)
  (setq layer (strcase (cdr (assoc 8 data))))
  (setq type (strcase (cdr (assoc 0 data))))
  (setq block (aab:entity-block data))
  (and (= layer (strcase (nth 0 rule)))
       (= type (strcase (nth 1 rule)))
       (= block (strcase (nth 2 rule)))))
(defun aab:remove-audited (/ selection index entity data remove rule count)
  (setq count 0 selection (ssget "_X" '((410 . "Model"))))
  (if selection
    (progn
      (setq index 0)
      (repeat (sslength selection)
        (setq entity (ssname selection index))
        (setq data (entget entity) remove nil)
        (if (not (aab:protected-layer-p (cdr (assoc 8 data))))
          (foreach rule *aab:removal-rules*
            (if (aab:matches-rule-p data rule) (setq remove T))))
        (if (and remove (entdel entity)) (setq count (1+ count)))
        (setq index (1+ index)))))
  count)
(defun aab:write-report (path / file item entity data layer status)
  (setq file (open path "w"))
  (if file
    (progn
      (write-line "\"HANDLE\";\"LAYER\";\"KIND\";\"STATUS\"" file)
      (foreach item *aab:assignments*
        (setq entity (handent (nth 0 item)))
        (if entity
          (progn (setq data (entget entity))
                 (setq layer (cdr (assoc 8 data)))
                 (setq status (if (= (strcase layer) (strcase (nth 1 item))) "OK" "DIVERGENTE")))
          (progn (setq layer "") (setq status "AUSENTE")))
        (write-line (strcat (aab:csv (nth 0 item)) ";"
          (aab:csv layer) ";" (aab:csv (nth 2 item)) ";"
          (aab:csv status)) file))
      (close file))))
(defun c:AAB_EXECUTAR_116H (/ item removed file)
  (foreach item *aab:assignments*
    (aab:set-layer (nth 0 item) (nth 1 item)))
  (setq removed (aab:remove-audited))
  (aab:write-report "C:/Users/danil/OneDrive/Documentos/Automacao_CAD/03_Saidas/Execucoes_11.6H/3b44a6accefd43099fe3ea4580805c13/20260729-172336-e0544cf5600549959fbe016eabcbadce/resultado-entidades.csv")
  (setq file (open "C:/Users/danil/OneDrive/Documentos/Automacao_CAD/03_Saidas/Execucoes_11.6H/3b44a6accefd43099fe3ea4580805c13/20260729-172336-e0544cf5600549959fbe016eabcbadce/resultado-limpeza.csv" "w"))
  (if file (progn (write-line "\"REMOVIDOS\"" file)
    (write-line (strcat "\"" (itoa removed) "\"") file)
    (close file)))
  (princ))
