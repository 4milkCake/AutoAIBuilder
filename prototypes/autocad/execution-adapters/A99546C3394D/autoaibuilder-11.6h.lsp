(vl-load-com)
(setq *aab:legend-handles* '("21BD94E" "21BD8DB" "21BD9D3" "21BD995" "21BD994" "21BD993" "21BD992" "21BD991" "21BD990" "21BD98F" "21BD98E" "21BD98D" "21BD98C" "21BD98A" "21BD989" "21BD97E" "21BD97D" "21BD97C" "21BD97B" "21BD97A" "21BD979" "21BD978" "21BD977" "21BD976" "21BD975" "21BD974" "21BD973" "21BD972" "21BD971" "21BD970" "21BD96D" "21BD96C" "21BD96B" "21BD969" "21BD967" "21BD966" "21BD965" "21BD964" "21BD963" "21BD962" "21BD961" "21BD960" "21BD95F" "21BD95E" "21BD95D" "21BD955" "21BD954" "21BD953" "21BD952" "21BD951" "21BD950" "21BD94F" "21BD94D" "21BD94C" "21BD94B" "21BD94A" "21BD949" "21BD948" "21BD947" "21BD946" "21BD945" "21BD944" "21BD940" "21BD93E" "21BD93D" "21BD93C" "21BD93B" "21BD93A" "21BD939" "21BD938" "21BD937" "21BD936" "21BD934" "21BD933" "21BD932" "21BD931" "21BD930" "21BD92F" "21BD92E" "21BD92D" "21BD92C" "21BD92B" "21BD92A" "21BD929" "21BD928" "21BD927" "21BD926" "21BD925" "21BD924" "21BD923" "21BD922" "21BD921" "21BD920" "21BD91F" "21BD91E" "21BD91D" "21BD91C" "21BD91B" "21BD91A" "21BD917" "21BD916" "21BD915" "21BD914" "21BD913" "21BD912" "21BD911" "21BD910" "21BD90F" "21BD90E" "21BD90D" "21BD90C" "21BD90B" "21BD90A" "21BD909" "21BD908" "21BD907" "21BD906" "21BD905" "21BD904" "21BD903" "21BD902" "21BD901" "21BD900" "21BD8FF" "21BD8FE" "21BD8FD" "21BD8FC" "21BD8FB" "21BD8FA" "21BD8F9" "21BD8F8" "21BD8F7" "21BD8F6" "21BD8F5" "21BD8F4" "21BD8F3" "21BD8F2" "21BD8F1" "21BD8F0" "21BD8EF" "21BD8EE" "21BD8ED" "21BD8EC" "21BD8EB" "21BD8EA" "21BD8E9" "21BD8E8" "21BD8E7" "21BD8E6" "21BD8E5" "21BD8E4" "21BD8E3" "21BD8E2" "21BD8E1" "21BD8E0" "21BD8DF" "21BD8DE" "21BD8DD" "21BD8DC" "21BD8DA" "21BD8D9" "21BD8D8" "21BD8D7" "21BD8D6" "21BD8D5" "21BD8D4" "21BD8D3" "21BD8D2" "21BD8D1" "21BD8D0" "21BD8CF" "21BD8CE" "21BD8CD" "21BD8CC" "21BD8CB" "21BD8CA" "21BD8C9" "21BD8C8" "21BD8C7" "21BD985" "21BD984" "21BD983" "21BD982" "21BD981" "21BD980" "21BD97F" "21BD96F" "21BD96E" "21BD96A" "21BD968" "21BD95C" "21BD95B" "21BD95A" "21BD959" "21BD958" "21BD957" "21BD956" "21BD943" "21BD942" "21BD941" "21BD93F" "21BD935" "23199A1" "2319964" "2319963" "21BD9E6" "21BD9E5" "21BD9E4" "21BD9E3" "21BD9E2" "21BD9E1" "21BD9E0" "21BD9DF" "21BD9DE" "21BD9DD" "21BD9DC" "21BD9DB" "21BD9DA" "21BD9D9" "21BD9D8" "21BD9D6" "21BD9D5" "21BD9D1" "21BD9D0" "21BD9CF" "21BD9CE" "21BD9CD" "21BD9CC" "21BD9CB" "21BD9CA" "21BD9C9" "21BD9C8" "21BD9C7" "21BD9C6" "21BD9C4" "21BD9C3" "21BD9C2" "21BD9C1" "21BD9C0" "21BD9BF" "21BD9BE" "21BD9BD" "21BD9BC" "21BD9BB" "21BD9BA" "21BD9B9" "21BD9B8" "21BD9B6" "21BD9B5" "21BD9B4" "21BD9B3" "21BD9B2" "21BD9B1" "21BD9B0" "21BD9AF" "21BD9AE" "21BD9AD" "21BD9AC" "21BD9D7" "21BD9AB" "21BD9AA" "21BD9A8" "21BD9A7" "21BD9A6" "21BD9A5" "21BD9A4" "21BD9A3" "21BD9A2" "21BD9A1" "21BD9A0" "21BD99F" "21BD99E" "21BD99C" "21BD99A" "21BD999" "21BD98B" "21BD988" "21BD986" "21BD8C4" "21BD8C3" "21BD8C1" "21BD8C0" "21BD8BF" "21BD8BE" "21BD8BD" "21BD8BC" "21BD8BB" "21BD8BA" "21BD8B9" "21BD8B8" "21BD8B7" "21BD8B6" "21BD8B5" "21BD8B4" "21BD8B2" "21BD8B1" "21BD8B0" "21BD8AF" "21BD8AE" "21BD8AD" "21BD8AC" "21BD8AB" "21BD8AA" "21BD8A9" "21BD8A8" "21BD8A7" "21BD8A6" "21BD8A5" "21BD8A4" "21BD8A3" "21BD8A2" "21BD8A1" "21BD8A0" "21BD89F" "21BD89E" "21BD89D"))
(defun aab:legend-selection (/ result entity)
  (setq result (ssadd))
  (foreach handle *aab:legend-handles*
    (setq entity (handent handle))
    (if entity (ssadd entity result)))
  result)
(defun aab:csv (value)
  (strcat "\"" value "\""))
(defun aab:write-report (/ file plan entry entity data layer)
  (setq file (open "C:/Users/danil/OneDrive/Documentos/Automacao_CAD/03_Saidas/Execucoes_11.6H/3b44a6accefd43099fe3ea4580805c13/20260729-170855-bedde22673214428ac67349a87d0ba71/resultado-pontos.csv" "w"))
  (if file
    (progn
      (write-line "\"HANDLE\";\"LAYER\"" file)
      (setq plan (mcad5:point-plan))
      (foreach entry plan
        (setq entity (nth 3 entry))
        (setq data (entget entity))
        (setq layer (cdr (assoc 8 data)))
        (write-line
          (strcat (aab:csv (nth 0 entry)) ";" (aab:csv layer)) file))
      (close file)))
  (princ))
